module ietf-bgp-origin-as-validation {
  yang-version "1.1";
  namespace "urn:ietf:params:xml:ns:yang:"
          + "ietf-bgp-origin-as-validation";
  prefix "oav";

  import ietf-yang-types {
       prefix "yang";
       reference
         "RFC 6991: Common YANG Data Types.";
  }

  import ietf-inet-types {
    prefix "inet";
    reference
      "RFC 6991: Common YANG Data Types";
  }

  import ietf-routing {
    prefix "rt";
    reference
      "RFC 8349, A YANG Data Model for Routing Management
       (NMDA Version).";
  }

  import ietf-bgp {
    prefix "bgp";
    reference
      "RFC XXXX: YANG Model for Border Gateway Protocol (BGP-4)";
  }

  import iana-bgp-types {
    prefix "bt";
    reference
      "RFC XXXX: YANG Model for Border Gateway Protocol (BGP-4)";
  }

  import iana-bgp-rib-types {
    prefix "brt";
    reference
      "RFC XXXX: YANG Model for Border Gateway Protocol (BGP-4)";
  }

  import ietf-routing-policy {
    prefix rt-pol;
    reference
      "RFC 9067: A YANG Data Model for Routing Policy Management.";
  }

  organization
    "IETF SIDROPS Working Group";

  contact
    "TBD";

  description
    "This module describes configuration of the BGP origin AS
     validation.

     This YANG model conforms to the Network Management
     Datastore Architecture (NMDA) as described in RFC 8342.

     Copyright (c) 2022 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  reference "RFC XXXX";

  revision 2022-10-18 {
    description
      "Initial Version";
    reference
      "RFC XXXX, YANG Data Model for RPKI to Router Protocol";
  }

  identity ineligible-orgin-as {

    base brt:ineligible-route-reason;
    description
      "Route was ineligible due to origin as validation";
  }

  typedef route-validity-invalid-reason {
    type enumeration {
      enum ineligible-orgin-as {
        description
          "Route was ineligible due to origin as number mismatch";
      }
      enum ineligible-max-len {
        description
          "Route was ineligible due to prefix maximum length
mismatch";
      }
    }
    description
    "Origin AS validation state invalid reason of BGP routes.";
  }

  typedef origin-as-validity-state {
    type enumeration {
      enum not-found {
        description
          "No VRP Covers the Route Prefix.";
      }
      enum valid {
        description
          "At least one VRP Matches the Route Prefix.";
      }
      enum invalid {
        description
          "At least one VRP Covers the Route Prefix, but no VRP
           Matches it.";
      }
      enum disabled {
        description
          "BGP origin AS validation is not enabled.";
      }
    }
    description
      "Origin AS validation state of BGP routes.";
    reference
      "RFC 6811, BGP Prefix Origin Validation.";
  }

  grouping origin-as-validation-config {

    description
      "Origin AS validation of BGP prefix.";
    container origin-as-validation {
      leaf enabled {
        type boolean;
        default "false";
        description
          "Whether origin-AS validation of BGP prefix is enabled.";
      }
      leaf eligible-prefix-policy {
        type leafref {
          path "/rt-pol:routing-policy/rt-pol:policy-definitions/"
                + "rt-pol:policy-definition/rt-pol:name";
           }
        description
          "A reference to a routing policy which can be used to
           restrict the prefixes for which Origin AS validation
           is enabled.";
      }
      leaf redistribution-as {
        type inet:as-number;
        description
          "Uses this AS number in the origin-AS validation for
           redistributed routes since they have no AS-PATH.";
        reference
          "RFC 8481, Clarifications to BGP Origin Validation Based
           on Resource Public Key Infrastructure (RPKI).";
      }
      description
        "Origin AS validation of BGP prefix.";
    }
  }

  grouping origin-as-selection-option {
    description
      "Origin AS option for BGP route selection.";
    container origin-as {
      leaf enabled {
        type boolean;
        default "false";
        description
          "When enabled allows the origin AS validity states to be
           taken into consideration in the best-path calculation.";
      }
      leaf allow-invalid {
        type boolean;
        default "false";
        description

          "When enabled allows the route with 'invalid' origin AS
           to be taken into consideration in the best-path
           calculation.";
      }
      leaf allow-not-found {
        type boolean;
        default "true";
        description
          "When enabled allows the route with 'not-found' origin
           AS to be taken into consideration in the best-path
           calculation.";
      }
      leaf eligible-prefix-policy {
        type leafref {
          path "/rt-pol:routing-policy/rt-pol:policy-definitions/"
                + "rt-pol:policy-definition/rt-pol:name";
           }
        description
          "A reference to a routing policy which can be used to
           restrict the prefixes for which Origin AS option
           is enabled for BGP route selection.";
      }
      description
        "Origin AS option for BGP route selection.";
    }
  }

  grouping origin-as-validity-advertisement {
    description
      "Advertisement of Origin Validation State Extended
       Community to neighbor(s).";
    leaf send-origin-as-validity {
      type boolean;
      default "false";
      description
        "If set to true, send the origin AS validity to the
         neighbor(s) using Origin Validation State Extended
         Community";
      reference
        "RFC 8097, BGP Prefix Origin Validation State Extended
         Community.";
    }
    leaf eligible-prefix-policy {
      type leafref {
        path "/rt-pol:routing-policy/rt-pol:policy-definitions/"
              + "rt-pol:policy-definition/rt-pol:name";
           }
      description

        "A reference to a routing policy which can be used to
         restrict the prefixes for which Origin Validation
         State Extended Community is advertised.";
    }
  }

  grouping export-origin-as-validation-config {
    description
      "Export Origin AS validation of BGP prefix.";
    container export-origin-as-validation {
      leaf enabled {
        type boolean;
        default "false";
        description
          "When enabled allows the origin AS validity states to be
           taken into consideration in BGP export.";
      }
      leaf allow-not-found {
        type boolean;
        default "false";
        description
          "When enabled allows the route with 'not-found' origin
           AS to be sent to the neighbor.";
      }
      leaf eligible-prefix-policy {
        type leafref {
          path "/rt-pol:routing-policy/rt-pol:policy-definitions/"
                + "rt-pol:policy-definition/rt-pol:name";
           }
        description
          "A reference to a routing policy which can be used to
           restrict the prefixes for which Origin AS validity
           states are considered in BGP export.";
      }
      description
        "Export Origin AS validation of BGP prefix.";
      reference
        "RFC 8893, Resource Public Key Infrastructure (RPKI) Origin
        Validation for BGP Export.";
       }
     }

  grouping origin-as-validity-statistics {
       description
         "Origin-AS validation statistics.";
       container statistics {
         leaf validation-state-unverified {
           type yang:gauge32;

           description
             "The number of routes with validation state as
unverified.";
         }
         leaf validation-state-unknown {
           type yang:gauge32;
           description
             "The number of routes with validation state as
unknown.";
         }
         leaf validation-state-invalid {
           type yang:gauge32;
           description
             "The number of routes with validation state as
invalid.";
         }
         leaf validation-state-valid {
           type yang:gauge32;
           description
             "The number of routes with validation state as valid.";
         }
         description
           "Statistical data for Origin-AS validation states.";
    }
  }

  augment "/rt:routing/rt:control-plane-protocols"
        + "/rt:control-plane-protocol/bgp:bgp/bgp:global"
        + "/bgp:afi-safis/bgp:afi-safi/bgp:ipv4-unicast" {
    description
      "Origin AS validation augmentation of BGP IPv4 Unicast
       Address Family.";
    uses origin-as-validation-config;
  }

  augment "/rt:routing/rt:control-plane-protocols"
        + "/rt:control-plane-protocol/bgp:bgp/bgp:global"
        + "/bgp:afi-safis/bgp:afi-safi/bgp:ipv6-unicast" {
    description
      "Origin AS validation augmentation of BGP IPv6 Unicast
       Address Family.";
    uses origin-as-validation-config;
  }

  augment "/rt:routing/rt:control-plane-protocols"
        + "/rt:control-plane-protocol/bgp:bgp/bgp:rib"
        + "/bgp:afi-safis/bgp:afi-safi/bgp:ipv4-unicast"
           + "/bgp:neighbors/bgp:neighbor/bgp:adj-rib-in-pre" {
       description
         "Augmentation of BGP IPv4 Unicast route statistics.";

       uses origin-as-validity-statistics;
     }

     augment "/rt:routing/rt:control-plane-protocols"
           + "/rt:control-plane-protocol/bgp:bgp/bgp:rib"
           + "/bgp:afi-safis/bgp:afi-safi/bgp:ipv6-unicast"
           + "/bgp:neighbors/bgp:neighbor/bgp:adj-rib-in-pre" {
       description
         "Augmentation of BGP IPv6 Unicast route statistics.";

       uses origin-as-validity-statistics;
     }

     augment "/rt:routing/rt:control-plane-protocols"
           + "/rt:control-plane-protocol/bgp:bgp/bgp:rib"
           + "/bgp:afi-safis/bgp:afi-safi/bgp:ipv4-unicast"
           + "/bgp:neighbors/bgp:neighbor/bgp:adj-rib-in-post" {
       description
         "Augmentation of BGP IPv4 Unicast route statistics.";

       uses origin-as-validity-statistics;
     }

     augment "/rt:routing/rt:control-plane-protocols"
           + "/rt:control-plane-protocol/bgp:bgp/bgp:rib"
           + "/bgp:afi-safis/bgp:afi-safi/bgp:ipv6-unicast"
           + "/bgp:neighbors/bgp:neighbor/bgp:adj-rib-in-post" {
       description
         "Augmentation of BGP IPv6 Unicast route statistics.";

       uses origin-as-validity-statistics;
     }

     augment "/rt:routing/rt:control-plane-protocols"
           + "/rt:control-plane-protocol/bgp:bgp/bgp:rib"
           + "/bgp:afi-safis/bgp:afi-safi/bgp:ipv4-unicast"
           + "/bgp:loc-rib" {
       description
         "Augmentation of BGP IPv4 Unicast route statistics.";

       uses origin-as-validity-statistics;
     }

     augment "/rt:routing/rt:control-plane-protocols"
           + "/rt:control-plane-protocol/bgp:bgp/bgp:rib"
           + "/bgp:afi-safis/bgp:afi-safi/bgp:ipv6-unicast"
           + "/bgp:loc-rib" {
       description
         "Augmentation of BGP IPv6 Unicast route statistics.";

       uses origin-as-validity-statistics;
     }

     augment "/rt:routing/rt:control-plane-protocols"
           + "/rt:control-plane-protocol/bgp:bgp/bgp:rib"
           + "/bgp:afi-safis/bgp:afi-safi/bgp:ipv4-unicast"
           + "/bgp:neighbors/bgp:neighbor/bgp:adj-rib-out-pre" {
       description
         "Augmentation of BGP IPv4 Unicast route statistics.";

       uses origin-as-validity-statistics;
     }

     augment "/rt:routing/rt:control-plane-protocols"
           + "/rt:control-plane-protocol/bgp:bgp/bgp:rib"
           + "/bgp:afi-safis/bgp:afi-safi/bgp:ipv6-unicast"
           + "/bgp:neighbors/bgp:neighbor/bgp:adj-rib-out-pre" {
       description
         "Augmentation of BGP IPv6 Unicast route statistics.";

       uses origin-as-validity-statistics;
     }

     augment "/rt:routing/rt:control-plane-protocols"
           + "/rt:control-plane-protocol/bgp:bgp/bgp:rib"
           + "/bgp:afi-safis/bgp:afi-safi/bgp:ipv4-unicast"
           + "/bgp:neighbors/bgp:neighbor/bgp:adj-rib-out-post" {
       description
         "Augmentation of BGP IPv4 Unicast route statistics.";

       uses origin-as-validity-statistics;
     }

     augment "/rt:routing/rt:control-plane-protocols"
           + "/rt:control-plane-protocol/bgp:bgp/bgp:rib"
           + "/bgp:afi-safis/bgp:afi-safi/bgp:ipv6-unicast"
           + "/bgp:neighbors/bgp:neighbor/bgp:adj-rib-out-post" {
       description
         "Augmentation of BGP IPv6 Unicast route statistics.";

       uses origin-as-validity-statistics;
     }

     augment "/rt:routing/rt:control-plane-protocols"
           + "/rt:control-plane-protocol/bgp:bgp/bgp:rib"
           + "/bgp:afi-safis/bgp:afi-safi/bgp:ipv4-unicast"
        + "/bgp:loc-rib/bgp:routes/bgp:route" {
    description
      "Origin AS validity augmentation of BGP IPv4 Unicast
       route.";
    leaf origin-as-validity {
      type origin-as-validity-state;
      description
        "Origin AS validity of BGP IPv4 Unicast prefix";
       }
       leaf validity-invalid-reason {
         type route-validity-invalid-reason;
         description
           "Reason for marking a BGP IPv4 Unicast prefix as
invalid";
    }
  }

  augment "/rt:routing/rt:control-plane-protocols"
        + "/rt:control-plane-protocol/bgp:bgp/bgp:rib"
        + "/bgp:afi-safis/bgp:afi-safi/bgp:ipv6-unicast"
        + "/bgp:loc-rib/bgp:routes/bgp:route" {
    description
      "Origin AS validity augmentation of BGP IPv6 Unicast
       route.";
    leaf origin-as-validity {
      type origin-as-validity-state;
      description
        "Origin AS validity of BGP IPv6 Unicast prefix";
       }
       leaf validity-invalid-reason {
         type route-validity-invalid-reason;
         description
           "Reason for marking a BGP IPv6 Unicast prefix as
invalid";
    }
  }

  augment "/rt:routing/rt:control-plane-protocols"
        + "/rt:control-plane-protocol/bgp:bgp/bgp:global"
        + "/bgp:afi-safis/bgp:afi-safi"
        + "/bgp:route-selection-options" {
    when "derived-from-or-self(../bgp:name, 'bt:ipv4-unicast') or "
       + "derived-from-or-self(../bgp:name, 'bt:ipv6-unicast')" {
      description
        "This augmentation is valid for IPv4 and IPv6 Unicast.";
    }
    description
      "augmentation of BGP route selection options";
    uses origin-as-selection-option;
  }

  augment "/rt:routing/rt:control-plane-protocols"
        + "/rt:control-plane-protocol/bgp:bgp/bgp:neighbors"
        + "/bgp:neighbor/bgp:afi-safis/bgp:afi-safi"
        + "/bgp:ipv4-unicast" {
    description
      "augmentation of Origin Validation State Extended
       Community advertisement for IPv4 Unicast neighbor";
    uses origin-as-validity-advertisement;
    uses export-origin-as-validation-config;
       uses origin-as-validity-statistics;
  }

  augment "/rt:routing/rt:control-plane-protocols"
        + "/rt:control-plane-protocol/bgp:bgp/bgp:neighbors"
        + "/bgp:neighbor/bgp:afi-safis/bgp:afi-safi"
        + "/bgp:ipv6-unicast" {
    description
      "augmentation of Origin Validation State Extended
       Community advertisement for IPv6 Unicast neighbor";
    uses origin-as-validity-advertisement;
    uses export-origin-as-validation-config;
       uses origin-as-validity-statistics;
  }

  augment "/rt:routing/rt:control-plane-protocols"
        + "/rt:control-plane-protocol/bgp:bgp/bgp:peer-groups"
        + "/bgp:peer-group/bgp:afi-safis/bgp:afi-safi"
        + "/bgp:ipv4-unicast" {
    description
      "augmentation of Origin Validation State Extended
       Community advertisement for IPv4 Unicast peer group";
    uses origin-as-validity-advertisement;
    uses export-origin-as-validation-config;
  }

  augment "/rt:routing/rt:control-plane-protocols"
        + "/rt:control-plane-protocol/bgp:bgp/bgp:peer-groups"
        + "/bgp:peer-group/bgp:afi-safis/bgp:afi-safi"
        + "/bgp:ipv6-unicast" {
    description
      "augmentation of Origin Validation State Extended
       Community advertisement for IPv6 Unicast peer group";
    uses origin-as-validity-advertisement;
    uses export-origin-as-validation-config;
  }
}
